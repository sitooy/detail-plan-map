FME workspace asemakaava_MALLI.fmw
Title: Ajantasa-asemakaava-aineiston luokittelu
Description: Aineiston yhtenäinen luokittelu WMS-julkaisua varten. Vienti PostGis-tietokantaan.
Usage: Avoimen lisenssin ehdoin, tarkentuu.
History: 20.10.2015,Mari Raussi / Sito,Irrotettu ensimmäinen versio yhteiseen käyttöön.
Legal terms conditions: Tähän tulee kuvaus avoimen lisenssin käyttöehdoista.

Note: DGNV8 Reader / Julkaise parametrit: / -fme_basename, / -fme_rotation, / -idgs_insertion_x, / -idgs_insertion_y, / -idgs_level_name / Settings: / Expand Named cells: YES / Expand Unnamed cells: YES / Drop Comlex Chain/Shapes: YES
Note: Vaihdetaan koordinaatisto
Reprojector
    DEST = EPSG:3067
    SOURCE = EPSG:3881
    INTERPOLATION_TYPE_NAME = Nearest Neighbor
    RASTER_CELL_SIZE = Preserve Cells
    REPROJECTED -> AttributeCreator_2
Note: Lisätään attribuutit: / tiedoston ja tason nimi
AttributeCreator_2
    ATTR_LIST = orig_lvl,@Value(igds_level_name),orig_file,@Value(fme_basename)
    -> GeometryFilter
GeometryFilter
    GEOM_PORT_NAMES = Line Arc Area Ellipse Text
    BREAK_AGG = No
    ELLIPSE -> Joiner_2
    AREA -> Joiner_2
    TEXT -> Joiner_3
    LINE -> Joiner_4
    ARC -> Joiner_4
Note: Erotetaan alueista kuvaustekniikassa / viivoina esitettävät kohteet
AttributeFilter_4
    ATTR_VALUES = <EMPTY>,<MISSING>,<NULL>,<UNFILTERED>,viiva_pistekatko,kayttotark_L,viiva_ohut,tontti_alue,viiva_pitkakatko,viiva_paksu,viiva_kapea
    ATTR_NAME = xls__LUOKKA
    <UNFILTERED> -> AttributeRenamer_2
    viiva_pistekatko -> GeometryExtractor_3
    viiva_ohut -> GeometryExtractor_3
    kayttotark_L -> GeometryExtractor_3
    kayttotark_L -> AttributeRenamer_2
    viiva_pitkakatko -> GeometryExtractor_3
    viiva_paksu -> GeometryExtractor_3
    viiva_kapea -> GeometryExtractor_3
AttributeFilter_2
    ATTR_VALUES = <EMPTY>,<MISSING>,<NULL>,<UNFILTERED>
    ATTR_NAME = xls__LUOKKA
    <UNFILTERED> -> AttributeRenamer
AttributeRenamer
    ATTR_LIST = xls__LUOKKA,luokka,
    -> BoundsExtractor_2
AttributeFilter_5
    ATTR_VALUES = <EMPTY>,<MISSING>,<NULL>,offset,<UNFILTERED>,pois
    ATTR_NAME = luokka
    <UNFILTERED> -> GeometryValidator_2
    offset -> AttributeFilter
Note: Tarkistetaan geometria ennen kantaan vientiä
Note: Postgis / Taulu: ak_viivat_kuntanumero / Sarakkeet: id, luokka, orig_lvl, orig_file
GeometryValidator_2
    TYPE_REPAIR = TYPE_REPAIR
    DUP_COORDS_CHECK_Z = Yes
    REPAIR = Yes
    CONSECUTIVE_IDENTICAL_VERTICES_2D = CONSECUTIVE_IDENTICAL_VERTICES_2D
    CHECK_HOLE_TOUCHING_POLYGON = No
    SELF_INTERSECTING = SELF_INTERSECTING
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    ARC_ENDPOINT_TOLERANCE_MODE = Auto
    NULL_REMOVAL = NULL_REMOVAL
    ISSUE_ATTR_NAME = _issues
    PRESETS = Custom
    NAN_REMOVAL = NAN_REMOVAL
    PASSED -> LINES
    REPAIRED -> LINES
LINES: Inspector [off]
    TACKATTRS = luokka
AttributeRenamer_2
    ATTR_LIST = xls__LUOKKA,luokka,,xls__HEX,color,
    -> AttributeCreator
AttributeCreator
    ATTR_LIST = color,#@Value(color)
    -> GeometryExtractor
AttributeFilter_6
    ATTR_VALUES = <EMPTY>,<MISSING>,<NULL>,<UNFILTERED>,pois,istutettava_alue
    ATTR_NAME = luokka
    <UNFILTERED> -> GeometryValidator
    istutettava_alue -> DonutBuilder
DonutBuilder
    ALLOW_CYCLES = No
    DROP = yes
    FLAG_ATTR = _hole_flag
    AREA -> GeometryValidator
    AREA -> DonutBuilder_Area
GeometryValidator
    TYPE_REPAIR = TYPE_REPAIR
    DUP_COORDS_CHECK_Z = Yes
    REPAIR = Yes
    CONSECUTIVE_IDENTICAL_VERTICES_2D = CONSECUTIVE_IDENTICAL_VERTICES_2D
    CHECK_HOLE_TOUCHING_POLYGON = No
    SELF_INTERSECTING = SELF_INTERSECTING
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    ARC_ENDPOINT_TOLERANCE_MODE = Auto
    NULL_REMOVAL = NULL_REMOVAL
    ISSUE_ATTR_NAME = _issues
    PRESETS = Custom
    NAN_REMOVAL = NAN_REMOVAL
    PASSED -> AREAS
    REPAIRED -> AREAS
    REPAIRED -> Sorter
    PASSED -> Sorter
Note: Postgis / Taulu: ak_alueet / Sarakkeet: id, luokka, orig_lvl, orig_file,color
Sorter
    SORT_PARM = luokka ALPHA ASCENDING
AREAS: Inspector [off]
DonutBuilder_Area: Inspector [off]
Note: Yhdistä luokitteluExceliin
Joiner_3
    DATASET = E:\Aineistot\Liiteri\asemakaavapalvelu\Kohdeluokat_luokittelu_25022015.xlsx
    TABLE = text
    XLSXR_EXCEL_COL_NAMES = YES
    JOIN_KEYS = igds_level_name "Level name"
    XLSXR_EXPOSED_ATTRS = xlsx_row_id,number(11,0)
    MATCH_RULE_DISPLAY = Match First (1:0..1+)
    XLSXR_EXPAND_MERGED_CELLS = Yes
    XLSXR_TABLELIST = text area line point
    ADDED_FIELDS = Fonttikoko LUOKKA
    XLSXR_SCAN_SCHEMA_IF_DYNAMIC = No
    JOINED_ATTRIBUTE_PREFIX = xls_
    XLSXR_SCHEMA = text,0,YM-merkintä,char,181,,,1,B,string,,,,2,C,string,,,,3,D,string,,,,4,E,string,,,,5,"Element count",number,5," 0",,6,"Level name",char,55,,,7,"Tarkista / Huomioi",char,120,,,8,LUOKKA,char,13,,,9,Fonttikoko,string,,,,10,italic,string,,,,11,bold,string,,,,12,underline,string,,,,1,,,,NO,NO,1,//tsclient/W/Ympäristöministeriö/TTE61407_10142670_Liiteri_Asemakaavapalvelu/50_03_Työluonnokset/Kohdeluokat_luokittelu_Mari11022015.xlsx,"0,0,12,34",Taul1,NO,area,0,YM-merkintä,char,51,,,1,Väri/Kuvio,char,37,,,2,PMS,number,5," 0",,3,RGB,char,13,,,4,HEX,char,7,,,5,"Element count",number,5," 0",,6,"Level name",char,67,,,7,Tarkista,char,23,,,8,LUOKKA,char,18,,,9,Overlay/pohjafill/noShow,char,10,,,10,hatch,string,,,,1,,,,NO,NO,1,,"0,0,10,45",,NO,line,0,YM-merkintä,char,181,,,1,Väri/Kuvio,char,47,,,2,PMS,string,,,,3,RGB,string,,,,4,HEX,string,,,,5,"Element count",number,6," 0",,6,"Level name",char,66,,,7,"Tarkista / Huomioi",char,123,,,8,LUOKKA,char,21,,,9,paksuus_,char,108,,,10,symbol_name,string,,,,1,,,,NO,NO,1,,"0,0,10,76",,NO,point,0,"Pisteitä ei siirretä !",string,,,,1,B,string,,,,2,C,string,,,,3,D,string,,,,4,E,string,,,,5,"Element count",number,3," 0",,6,"Level name",char,64,,,1,,,,NO,NO,1,,"0,0,6,17",,NO
    FORMAT = XLSXR
    XLSXR_USE_SCHEMA_OTHER_FILES = No
    XLSXR_READ_BLANK_AS = Missing
    XLSXR_FORCE_DATETIME = NO
    JOINED -> AttributeRenamer_3
AttributeRenamer_3
    ATTR_LIST = xls__LUOKKA,luokka,,xls__Fonttikoko,fontsize,
    -> AttributeFilter_3
AttributeFilter_3
    ATTR_VALUES = <EMPTY>,<MISSING>,<NULL>,<UNFILTERED>,kesken,pois,ohut,kaltevuus
    ATTR_NAME = luokka
    <UNFILTERED> -> VertexCreator
    kesken -> VertexCreator
    ohut -> VertexCreator
    kaltevuus -> AttributeCreator_9
    pois -> TARKISTUS
    <EMPTY> -> TARKISTUS
TARKISTUS: Inspector [off]
VertexCreator
    YVAL = @Value(igds_insertion_y)
    MODE_NAME = Add Point
    XVAL = @Value(igds_insertion_x)
    -> AttributeCreator_3
Note: Postgis / Taulu: ak_tekstit / Sarakkeet: id, luokka, orig_lvl, orig_file, rotation, string, fontsize
AttributeCreator_3
    ATTR_LIST = string,@Value(fme_text_string),rotation,@Value(fme_rotation)

Bookmark: Lisää luokka Excelin mukaan
Joiner_4
    DATASET = E:\Aineistot\Liiteri\asemakaavapalvelu\Kohdeluokat_luokittelu_25022015.xlsx
    TABLE = line
    XLSXR_EXCEL_COL_NAMES = YES
    JOIN_KEYS = igds_level_name "Level name"
    XLSXR_EXPOSED_ATTRS = xlsx_row_id,number(11,0)
    MATCH_RULE_DISPLAY = Match First (1:0..1+)
    XLSXR_EXPAND_MERGED_CELLS = Yes
    XLSXR_TABLELIST = line text area
    ADDED_FIELDS = LUOKKA
    XLSXR_SCAN_SCHEMA_IF_DYNAMIC = No
    JOINED_ATTRIBUTE_PREFIX = xls_
    XLSXR_SCHEMA = line,0,YM-merkintä,char,181,,,1,Väri/Kuvio,char,47,,,2,PMS,string,,,,3,RGB,string,,,,4,HEX,string,,,,5,"Element count",number,6,0,,6,"Level name",char,66,,,7,Tarkista,char,123,,,8,LUOKKA,char,21,,,9,paksuus_,char,108,,,10,symbol_name,string,,,,1,,,,NO,NO,1,E:/FME_ajot/liiteri/asemakaavat/Kohdeluokat_luokittelu_viivat.xlsx,"0,0,10,76","Taul1,point",NO,text,0,YM-merkintä,char,51,,,1,B,string,,,,2,C,string,,,,3,D,string,,,,4,E,string,,,,5,F,string,,,,6,YM-merkintä00,char,181,,,7,H,string,,,,8,I,string,,,,9,J,string,,,,10,K,string,,,,11,"Element count",number,5,0,,12,"Level name",char,55,,,13,"Tarkista / Huomioi",char,120,,,14,LUOKKA,char,13,,,15,Fonttikoko,string,,,,16,italic,string,,,,17,bold,string,,,,18,underline,string,,,,1,,,,NO,NO,1,,"0,0,18,34",,NO,area,0,YM-merkintä,char,51,,,1,Väri/Kuvio,char,37,,,2,PMS,number,5,0,,3,RGB,char,13,,,4,HEX,char,7,,,5,"Element count",number,5,0,,6,"Level name",char,67,,,7,Tarkista,char,23,,,8,LUOKKA,char,23,,,9,Overlay/pohjafill/noShow,char,10,,,10,hatch,string,,,,1,,,,NO,NO,1,,"0,0,10,45",,NO
    FORMAT = XLSXR
    XLSXR_FORCE_DATETIME = NO
    XLSXR_READ_BLANK_AS = Missing
    XLSXR_USE_SCHEMA_OTHER_FILES = No
    JOINED -> GeometryExtractor_3
Note: lisätään myös väriarvo, HEX
Joiner_2
    DATASET = E:\Aineistot\Liiteri\asemakaavapalvelu\Kohdeluokat_luokittelu_25022015.xlsx
    TABLE = area
    XLSXR_EXCEL_COL_NAMES = YES
    JOIN_KEYS = igds_level_name "Level name"
    XLSXR_EXPOSED_ATTRS = xlsx_row_id,number(11,0)
    MATCH_RULE_DISPLAY = Match First (1:0..1+)
    XLSXR_EXPAND_MERGED_CELLS = Yes
    XLSXR_TABLELIST = area
    ADDED_FIELDS = HEX LUOKKA
    XLSXR_SCAN_SCHEMA_IF_DYNAMIC = No
    JOINED_ATTRIBUTE_PREFIX = xls_
    XLSXR_SCHEMA = area,0,YM-merkintä,char,51,,,1,Väri/Kuvio,char,37,,,2,PMS,number,5," 0",,3,RGB,char,13,,,4,HEX,char,7,,,5,"Element count",number,5," 0",,6,"Level name",char,67,,,7,Tarkista,char,23,,,8,LUOKKA,char,18,,,9,Overlay/pohjafill/noShow,char,10,,,10,hatch,string,,,,1,,,,NO,NO,1,//tsclient/W/Ympäristöministeriö/TTE61407_10142670_Liiteri_Asemakaavapalvelu/50_03_Työluonnokset/Kohdeluokat_luokittelu.xlsx,"0,0,10,45","Taul1,text,line,point",NO
    FORMAT = XLSXR
    XLSXR_FORCE_DATETIME = NO
    XLSXR_READ_BLANK_AS = Missing
    XLSXR_USE_SCHEMA_OTHER_FILES = No
    JOINED -> AttributeFilter_4

Bookmark: Korjaa viivojen geometria
GeometryExtractor_3
    ATTR = _geometry
    KIND_LONG = GeoJSON
    -> GeometryReplacer_3
GeometryReplacer_3
    SOURCE = @Value(_geometry)
    REMOVE_ATTRIBUTE = Yes
    KIND_LONG = GeoJSON
    -> AttributeFilter_2

Bookmark: Duplikaatit pois
BoundsExtractor_2
    YMIN = _ymin
    YMAX = _ymax
    ZMIN = _zmin
    ZMAX = _zmax
    XMIN = _xmin
    XMAX = _xmax
    -> DuplicateRemover_2
DuplicateRemover_2
    KEYATTR = _xmax _xmin _ymax _ymin luokka
    UNIQUE -> AttributeFilter_5

Bookmark: Geometrian muokkausta kuvaustapaa varten: jalankulun poikkiviivoitukset ja ohjeellinen reuna, liikennealueen pallot ja hidaskatu
AttributeFilter
    ATTR_VALUES = <EMPTY>,<MISSING>,<NULL>,<UNFILTERED>,AK_LiikennointiViiva_Hidaskatu,AK_LiikennointiViiva_Jalankulku_a-osa_r_5m,AK_LiikennointiViiva_Jalankulku_a-osa_r_6m,AK_LiikennointiViiva_Jalankulku_a-osa_4m,AK_LiikennointiViiva_Jalankulku_a-osa,AK_LiikennointiViiva_Ohj_jalankulku,AK_LiikennointiViiva_Ohj_jalankulku_4m,AK_LiikennointiViiva_Ohj_jalankulku_r,AK_LiikennointiViiva_Ohj_jalankulku_r_4m,AK_LiikennointiViiva_Ohj_jalankulku__,AK_LiikennointiViiva_Ohj_jalankulku__4m,AK_LiikennointiViiva_Ohj_jalankulku__5m,AK_LiikennointiViiva_Ohj_jalankulku__6m,AK_LiikennointiViiva_Jalankulku_III,AK_LiikennointiViiva_Jalankulku_III_4m,AK_LiikennointiViiva_Jalankulku_III_5m,AK_LiikennointiViiva_Jalankulku_III_6m,AK_LiikennointiViiva_Jalankulku___,AK_LiikennointiViiva_Jalankulku___4m,AK_LiikennointiViiva_Jalankulku___5m,AK_LiikennointiViiva_Jalankulku___6m,AK_KayttotarkoitusSymboliViiva_Liikennealueen_kuvio,AK_KayttotarkoitusSymboliViiva_Rautatiealueen_kuvio
    ATTR_NAME = orig_lvl
    AK_KayttotarkoitusSymboliViiva_Rautatiealueen_kuvio -> AttributeCreator_7
    AK_KayttotarkoitusSymboliViiva_Liikennealueen_kuvio -> AttributeCreator_6
    AK_LiikennointiViiva_Jalankulku___6m -> lev
    AK_LiikennointiViiva_Jalankulku___ -> lev
    AK_LiikennointiViiva_Jalankulku___4m -> lev
    AK_LiikennointiViiva_Jalankulku___5m -> lev
    AK_LiikennointiViiva_Jalankulku_III -> lev_2
    AK_LiikennointiViiva_Jalankulku_III_4m -> lev_2
    AK_LiikennointiViiva_Jalankulku_III_5m -> lev_2
    AK_LiikennointiViiva_Jalankulku_III_6m -> lev_2
    AK_LiikennointiViiva_Ohj_jalankulku__6m -> lev_3
    AK_LiikennointiViiva_Ohj_jalankulku__5m -> lev_3
    AK_LiikennointiViiva_Ohj_jalankulku__ -> lev_3
    AK_LiikennointiViiva_Ohj_jalankulku__4m -> lev_3
    AK_LiikennointiViiva_Ohj_jalankulku_4m -> keskilinjasta_lev
    AK_LiikennointiViiva_Ohj_jalankulku -> keskilinjasta_lev
    AK_LiikennointiViiva_Ohj_jalankulku_r -> reunasta_kaikki
    AK_LiikennointiViiva_Ohj_jalankulku_r_4m -> reunasta_kaikki
    AK_LiikennointiViiva_Jalankulku_a-osa -> keskilinjasta_lev
    AK_LiikennointiViiva_Jalankulku_a-osa_4m -> keskilinjasta_lev
    AK_LiikennointiViiva_Jalankulku_a-osa_r_6m -> reunasta_kaikki
    AK_LiikennointiViiva_Jalankulku_a-osa_r_5m -> reunasta_kaikki
    AK_LiikennointiViiva_Hidaskatu -> hidaskatu_luokka
hidaskatu_luokka: AttributeCreator
    ATTR_LIST = luokka,hidaskatu
    -> GeometryValidator_2
reunasta_kaikki: AttributeValueMapper
    LUT = AK_LiikennointiViiva_Ohj_jalankulku_r,1.5,AK_LiikennointiViiva_Ohj_jalankulku_r_4m,2,AK_LiikennointiViiva_Jalankulku_a-osa_r_5m,2.5,AK_LiikennointiViiva_Jalankulku_a-osa_r_6m,3
    SRC = orig_lvl
    VAL_ATTR = _lev
    DIRECTION = Forward (Source To Destination)
    -> OffsetCurveGenerator_3
    -> pitkakatko_luokka
    -> lev_3

Bookmark: Keskilinjasta generoituvat
keskilinjasta_lev: AttributeValueMapper
    LUT = AK_LiikennointiViiva_Ohj_jalankulku,1.5,AK_LiikennointiViiva_Ohj_jalankulku_4m,2,AK_LiikennointiViiva_Ohj_jalankulku_r,1.5,AK_LiikennointiViiva_Ohj_jalankulku_r_4m,2,AK_LiikennointiViiva_Jalankulku_a-osa_4m,2,AK_LiikennointiViiva_Jalankulku_a-osa,1.5
    SRC = orig_lvl
    VAL_ATTR = _lev
    DIRECTION = Forward (Source To Destination)
    -> poikkiviiva_luokka
    -> OffsetCurveGenerator_5
OffsetCurveGenerator_5
    ANGLE = 22.5
    OFFSET = @Value(_lev)
    LEFT -> pitkakatko_luokka
    RIGHT -> pitkakatko_luokka

Bookmark: orig+left_pitkakatko
lev_3: AttributeValueMapper
    LUT = AK_LiikennointiViiva_Ohj_jalankulku__,3,AK_LiikennointiViiva_Ohj_jalankulku__4m,4,AK_LiikennointiViiva_Ohj_jalankulku__5m,5,AK_LiikennointiViiva_Ohj_jalankulku__6m,6,AK_LiikennointiViiva_Ohj_jalankulku_r,3,AK_LiikennointiViiva_Ohj_jalankulku_r_4m,4,AK_LiikennointiViiva_Jalankulku_a-osa_r_5m,5,AK_LiikennointiViiva_Jalankulku_a-osa_r_6m,6
    SRC = orig_lvl
    VAL_ATTR = _lev
    DIRECTION = Forward (Source To Destination)
    -> OffsetCurveGenerator_4
    -> pitkakatko_luokka
OffsetCurveGenerator_4
    ANGLE = 22.5
    OFFSET = @Value(_lev)
    LEFT -> pitkakatko_luokka
pitkakatko_luokka: AttributeCreator
    ATTR_LIST = luokka,viiva_pitkakatko
    -> GeometryValidator_2

Bookmark: Poikkiviivat
lev_2: AttributeValueMapper
    LUT = AK_LiikennointiViiva_Jalankulku_III,1.5,AK_LiikennointiViiva_Jalankulku_III_4m,2,AK_LiikennointiViiva_Jalankulku_III_5m,2.5,AK_LiikennointiViiva_Jalankulku_III_6m,3,AK_LiikennointiViiva_Ohj_jalankulku,"",AK_LiikennointiViiva_Ohj_jalankulku__,"",AK_LiikennointiViiva_Ohj_jalankulku__4m,"",AK_LiikennointiViiva_Ohj_jalankulku__5m,"",AK_LiikennointiViiva_Ohj_jalankulku__6m,"",AK_LiikennointiViiva_Ohj_jalankulku_4m,"",AK_LiikennointiViiva_Ohj_jalankulku_r,""
    SRC = orig_lvl
    VAL_ATTR = _lev
    DIRECTION = Forward (Source To Destination)
    -> OffsetCurveGenerator_3
OffsetCurveGenerator_3
    ANGLE = 22.5
    OFFSET = @Value(_lev)
    LEFT -> poikkiviiva_luokka
poikkiviiva_luokka: AttributeCreator
    ATTR_LIST = luokka,poikkiviiva@Value(_lev)
    -> GeometryValidator_2

Bookmark: orig+left_pistekatkoksi
lev: AttributeValueMapper
    LUT = AK_LiikennointiViiva_Jalankulku___,3,AK_LiikennointiViiva_Jalankulku___4m,4,AK_LiikennointiViiva_Jalankulku___5m,5,AK_LiikennointiViiva_Jalankulku___6m,6
    SRC = orig_lvl
    VAL_ATTR = _lev
    DIRECTION = Forward (Source To Destination)
    -> OffsetCurveGenerator_2
    -> pistekatko_luokka
OffsetCurveGenerator_2
    ANGLE = 22.5
    OFFSET = @Value(_lev)
    LEFT -> pistekatko_luokka
pistekatko_luokka: AttributeCreator
    ATTR_LIST = luokka,viiva_pistekatko
    -> GeometryValidator_2

Bookmark: liikennepallojen siirto 1m ja luokka offset ->Xalueen_reuna
AttributeCreator_6
    ATTR_LIST = luokka,liikennealue_reuna
    -> OffsetCurveGenerator
AttributeCreator_7
    ATTR_LIST = luokka,rautatiealue_reuna
    -> OffsetCurveGenerator
OffsetCurveGenerator
    ANGLE = 22.5
    OFFSET = 1
    LEFT -> GeometryValidator_2

Bookmark: Korjaa geometriat
GeometryExtractor
    ATTR = _geometry
    KIND_LONG = GeoJSON
    -> GeometryReplacer
GeometryReplacer
    SOURCE = @Value(_geometry)
    REMOVE_ATTRIBUTE = Yes
    KIND_LONG = GeoJSON
    -> BoundsExtractor

Bookmark: Duplikaatit pois
BoundsExtractor
    YMIN = _ymin
    YMAX = _ymax
    ZMIN = _zmin
    ZMAX = _zmax
    XMIN = _xmin
    XMAX = _xmax
    -> DuplicateRemover
DuplicateRemover
    KEYATTR = _xmax _xmin _ymax _ymin luokka
    UNIQUE -> AttributeFilter_6

Bookmark: Tarkistetaan, löytyykö tekstistä a
AttributeCreator_9
    ATTR_LIST = test,@FindString(@Value(fme_text_string),a)
    -> Tester_3
Tester_3
    TEST_CLAUSE = TEST @Value(test) = 0
    BOOL_OP = OR
    TEST_DESCRIPTION = Onko eka alpha
    TEST_MODE = Automatic
    PASSED -> AttributeCreator_10

Bookmark: Kattokaltevuuden erikoismerkit
Note: Postgis / Taulu: ak_tekstit / Sarakkeet: id, luokka, orig_lvl, orig_file, rotation, string, fontsize
AttributeCreator_10
    ATTR_LIST = a,@Left(@Value(fme_text_string),1),string,@Trim(@Value(fme_text_string),a)
    -> AttributeCreator_11
    -> VertexCreator_3

Bookmark: Alphalle piste
VertexCreator_3
    YVAL = @Value(igds_insertion_y)
    MODE_NAME = Add Point
    XVAL = @Value(igds_insertion_x)
    -> AttributeCreator_12
Note: Postgis / Taulu: ak_tekstit / Sarakkeet: id, luokka, orig_lvl, orig_file, rotation, string, fontsize
AttributeCreator_12
    ATTR_LIST = luokka,alpha,string,""

Bookmark: Kaltevuuden astemerkki (toteutus kesken)
AttributeCreator_11 [off]
    ATTR_LIST = aste,o
    -> AttributeFilter_3_kaltevuus
AttributeFilter_3_kaltevuus: Inspector
    TACKATTRS = luokka

FME custom transformer DonutHoleFilter
This transformer removes holes from donut polygons that are less than the user defined size. Non-donut features are left untouched.
Set the Minimum Hole Area to the desired size. All holes less than this size will be removed. If all holes are removed the feature will be demoted to a simple polygon.
This transformer will not modify any polygons that occupy the donut holes, but an AreaCalculator and Tester can be used to remove those as well.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- FILTER =   # Minimum Hole Area

INPUT (input)
    -> ParameterFetcher
Note: Fetch filter size
ParameterFetcher
    ATTR_LIST = _FILTER {$(FILTER)}
    -> PythonCaller_3
Note: Remove small holes
PythonCaller_3
    PYTHONSOURCE:
      import fmeobjects
      # Template Function interface:
      def removeSmallHoles(feature):
          gtype = feature.getAttribute('fme_geometry')
          filter = feature.getAttribute('_FILTER')
          # only process donuts
          if gtype == 'fme_donut':
              geom = feature.getGeometry()
              # create new donut geometry from outershell
              newgeom = fmeobjects.FMEDonut(geom.getOuterBoundaryAsCurve())
              # loop through inner shells
              for x in range(geom.numInnerBoundaries()):
                  boundary = geom.getInnerBoundaryAsCurveAt(x)
                  # create polygon to measure area
                  poly = fmeobjects.FMEPolygon(boundary)
                  area = poly.getArea()
                  # if shell is large enough copy to new donut geometry
                  if area > float(filter):
                      newgeom.addInnerBoundaryCurve(boundary)

              # replace old geometry with new
              feature.setGeometry(newgeom)
    PYTHONSYMBOL = removeSmallHoles
    -> GeometryRefiner
Note: If all holes removed, / revert to polygon
GeometryRefiner
    -> AttributeRemover
Note: Clean up feature
AttributeRemover
    REMOVE_ATTRS = _FILTER
    -> OUTPUT (output)
OUTPUT (output)
